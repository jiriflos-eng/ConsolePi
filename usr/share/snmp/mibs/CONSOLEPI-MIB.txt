CONSOLEPI-MIB DEFINITIONS ::= BEGIN

IMPORTS
    MODULE-IDENTITY, OBJECT-TYPE, enterprises, Integer32, Gauge32, Counter64, TimeTicks
        FROM SNMPv2-SMI
    DisplayString
        FROM SNMPv2-TC;

consolePi MODULE-IDENTITY
    LAST-UPDATED "202608170000Z"
    ORGANIZATION "ConsolePi"
    CONTACT-INFO "Local ConsolePi administrator"
    DESCRIPTION "Read-only operational metrics exported by ConsolePi."
    ::= { enterprises 55555 }

consolePiObjects OBJECT IDENTIFIER ::= { consolePi 1 }

consolePiCpuPercent OBJECT-TYPE
    SYNTAX Gauge32 (0..100)
    MAX-ACCESS read-only
    STATUS current
    DESCRIPTION "Instantaneous CPU utilisation in percent."
    ::= { consolePiObjects 1 }
consolePiCpuTemperatureDeciC OBJECT-TYPE
    SYNTAX Integer32
    MAX-ACCESS read-only
    STATUS current
    DESCRIPTION "CPU temperature in tenths of degrees Celsius."
    ::= { consolePiObjects 2 }
consolePiMemoryUsedBytes OBJECT-TYPE
    SYNTAX Counter64
    MAX-ACCESS read-only
    STATUS current
    DESCRIPTION "Used operational memory in bytes."
    ::= { consolePiObjects 3 }
consolePiMemoryTotalBytes OBJECT-TYPE
    SYNTAX Counter64
    MAX-ACCESS read-only
    STATUS current
    DESCRIPTION "Total operational memory in bytes."
    ::= { consolePiObjects 4 }
consolePiMemoryUsedPercent OBJECT-TYPE
    SYNTAX Gauge32 (0..100)
    MAX-ACCESS read-only
    STATUS current
    DESCRIPTION "Used operational memory in percent."
    ::= { consolePiObjects 5 }
consolePiDiskUsedBytes OBJECT-TYPE
    SYNTAX Counter64
    MAX-ACCESS read-only
    STATUS current
    DESCRIPTION "Used root filesystem capacity in bytes."
    ::= { consolePiObjects 6 }
consolePiDiskTotalBytes OBJECT-TYPE
    SYNTAX Counter64
    MAX-ACCESS read-only
    STATUS current
    DESCRIPTION "Total root filesystem capacity in bytes."
    ::= { consolePiObjects 7 }
consolePiDiskUsedPercent OBJECT-TYPE
    SYNTAX Gauge32 (0..100)
    MAX-ACCESS read-only
    STATUS current
    DESCRIPTION "Used root filesystem capacity in percent."
    ::= { consolePiObjects 8 }
consolePiUptime OBJECT-TYPE
    SYNTAX TimeTicks
    MAX-ACCESS read-only
    STATUS current
    DESCRIPTION "ConsolePi uptime."
    ::= { consolePiObjects 9 }

consolePiAvailableUpdates OBJECT-TYPE
    SYNTAX Gauge32
    MAX-ACCESS read-only
    STATUS current
    DESCRIPTION "Number of packages reported by the most recent ConsolePi update check."
    ::= { consolePiObjects 10 }
consolePiRebootRequired OBJECT-TYPE
    SYNTAX INTEGER { no(0), yes(1) }
    MAX-ACCESS read-only
    STATUS current
    DESCRIPTION "Whether the latest package update requires a reboot."
    ::= { consolePiObjects 11 }
consolePiEthernetLinkState OBJECT-TYPE
    SYNTAX INTEGER { up(1), down(2) }
    MAX-ACCESS read-only
    STATUS current
    DESCRIPTION "Operational state of the eth0 Ethernet link."
    ::= { consolePiObjects 12 }

consolePiServices OBJECT IDENTIFIER ::= { consolePiObjects 20 }
consolePiServiceTable OBJECT-TYPE
    SYNTAX SEQUENCE OF ConsolePiServiceEntry
    MAX-ACCESS not-accessible
    STATUS current
    DESCRIPTION "ConsolePi service state table."
    ::= { consolePiServices 1 }
ConsolePiServiceEntry ::= SEQUENCE {
    consolePiServiceIndex Integer32,
    consolePiServiceName DisplayString,
    consolePiServiceState Integer32
}
consolePiServiceEntry OBJECT-TYPE
    SYNTAX ConsolePiServiceEntry
    MAX-ACCESS not-accessible
    STATUS current
    DESCRIPTION "A ConsolePi service."
    INDEX { consolePiServiceIndex }
    ::= { consolePiServiceTable 1 }
consolePiServiceIndex OBJECT-TYPE
    SYNTAX Integer32 (1..255)
    MAX-ACCESS not-accessible
    STATUS current
    DESCRIPTION "Stable service index."
    ::= { consolePiServiceEntry 1 }
consolePiServiceName OBJECT-TYPE
    SYNTAX DisplayString
    MAX-ACCESS read-only
    STATUS current
    DESCRIPTION "systemd service name."
    ::= { consolePiServiceEntry 2 }
consolePiServiceState OBJECT-TYPE
    SYNTAX INTEGER { active(1), inactive(2) }
    MAX-ACCESS read-only
    STATUS current
    DESCRIPTION "Current systemd service state."
    ::= { consolePiServiceEntry 3 }

consolePiSerialPorts OBJECT IDENTIFIER ::= { consolePiObjects 30 }
consolePiSerialPortTable OBJECT-TYPE
    SYNTAX SEQUENCE OF ConsolePiSerialPortEntry
    MAX-ACCESS not-accessible
    STATUS current
    DESCRIPTION "Configured ConsolePi SSH serial-console ports."
    ::= { consolePiSerialPorts 1 }
ConsolePiSerialPortEntry ::= SEQUENCE {
    consolePiSerialPortSshPort Integer32,
    consolePiSerialPortLabel DisplayString,
    consolePiSerialPortState Integer32
}
consolePiSerialPortEntry OBJECT-TYPE
    SYNTAX ConsolePiSerialPortEntry
    MAX-ACCESS not-accessible
    STATUS current
    DESCRIPTION "A configured ConsolePi serial-console port."
    INDEX { consolePiSerialPortSshPort }
    ::= { consolePiSerialPortTable 1 }
consolePiSerialPortSshPort OBJECT-TYPE
    SYNTAX Integer32 (1..65535)
    MAX-ACCESS not-accessible
    STATUS current
    DESCRIPTION "SSH port used to access this serial console."
    ::= { consolePiSerialPortEntry 1 }
consolePiSerialPortLabel OBJECT-TYPE
    SYNTAX DisplayString
    MAX-ACCESS read-only
    STATUS current
    DESCRIPTION "ConsolePi label for this serial console."
    ::= { consolePiSerialPortEntry 2 }
consolePiSerialPortState OBJECT-TYPE
    SYNTAX INTEGER { unassigned(1), disconnected(2), connected(3) }
    MAX-ACCESS read-only
    STATUS current
    DESCRIPTION "Whether the configured serial adapter is assigned and physically present."
    ::= { consolePiSerialPortEntry 3 }

END
